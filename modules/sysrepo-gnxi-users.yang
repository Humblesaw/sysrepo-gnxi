module sysrepo-gnxi-users {
  yang-version 1.1;
  namespace "urn:sysrepo:gnxi:users";
  prefix sgu;

  import iana-crypt-hash {
    prefix ianach;
  }

  description
    "User database for the sysrepo-gnxi gNMI server.

     Defines users with (hashed) passwords. Authorization of these
     users is enforced by the sysrepo NACM implementation
     (ietf-netconf-acm) which grants access based on the authenticated
     username. This module deliberately holds no access-control data.

     This module is installed into sysrepo and its data is stored in
     the running datastore. It is private: it must never be accessible
     via gNMI RPCs. Protection is enforced by the NACM configuration
     (no rule-list should ever grant non-administrative users access to
     it) and by filesystem permissions (0600) on the module data file.";

  revision 2026-10-22 {
    description
      "Remove the per-user ACL list, user authorization is now
       enforced by sysrepo NACM (ietf-netconf-acm).";
  }

  revision 2026-08-26 {
    description "Install into sysrepo instead of a private libyang context.";
  }

  revision 2026-07-28 {
    description "Initial revision.";
  }

  container users {
    description "User database root container.";

    list user {
      key "name";
      description "A user account.";

      leaf name {
        type string {
          pattern '[a-zA-Z0-9_-]+';
        }
        description "Username (alphanumeric, dash, underscore only).";
      }

      leaf password {
        type ianach:crypt-hash;
        mandatory true;
        must "not(starts-with(., '$0$'))" {
          error-message
            "Plaintext passwords are not allowed, store a hash";
        }
        description
          "Password in the iana-crypt-hash crypt-hash format
           '$<id>$<salt>$<hash>' with the hash function identified by
           <id>: 1 (MD5-crypt), 5 (SHA-256-crypt) or 6 (SHA-512-crypt).
           The '$0$' cleartext form is not allowed.";
      }
    }
  }
}
