module sysrepo-gnxi-test-clash {
  yang-version 1.1;
  namespace "urn:sysrepo:gnxi:test-clash";
  prefix sgtc;

  organization
    "CESNET, z.s.p.o.";
  contact
    "Ondrej Kusnirik <kusnirik@cesnet.cz>";
  description
    "sysrepo-gnxi test module - its top-level node name clashes with
     gnmi-server-test to exercise ambiguous bare-name path resolution.

     Copyright (c) 2026 CESNET, z.s.p.o.

     Licensed under the Apache License, Version 2.0 (the 'License');
     you may not use this file except in compliance with the License.
     You may obtain a copy of the License at
     http://www.apache.org/licenses/LICENSE-2.0";

  revision 2026-10-05 {
    description "Initial revision.";
  }

  container test2 {
    leaf clash {
      type string;
    }
  }
}
