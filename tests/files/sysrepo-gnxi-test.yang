module sysrepo-gnxi-test {
  yang-version 1.1;
  namespace "urn:sysrepo:gnxi:test";
  prefix sgt;

  organization
    "CESNET, z.s.p.o.";
  contact
    "Ondrej Kusnirik <kusnirik@cesnet.cz>";
  description
    "sysrepo-gnxi test module.

     Copyright (c) 2025 Graphiant, Inc.
     Copyright (c) 2026 CESNET, z.s.p.o.

     Licensed under the Apache License, Version 2.0 (the 'License');
     you may not use this file except in compliance with the License.
     You may obtain a copy of the License at
     http://www.apache.org/licenses/LICENSE-2.0";

  revision 2021-02-10 {
    description "Initial revision.";
  }

  container test {
    list things {
      key "name";

      leaf name {
        type string;
      }

      leaf description {
        type string;
      }

      leaf enabled {
        type boolean;
      }

      leaf amount {
        type uint32;
      }

      leaf signed-amount {
        type int32;
      }

      leaf decimal-amount {
        type decimal64 {
          fraction-digits 2;
        }
      }

      leaf-list amount-history {
        type uint32;
      }
      leaf ready {
        type empty;
      }
    }
  }

  container test2 {
    leaf enabled {
      type boolean;
    }

    leaf enabled2 {
      type boolean;
    }

    leaf custom-error {
      type uint8;
      default 0;
    }

    leaf must-error {
      must "current() > 42";
      type uint8;
    }
  }

  container test-state {
    config false;
    list things {
      key "name";

      leaf name {
        type string;
      }

      leaf counter {
        type uint64;
      }

      leaf counter2 {
        type uint64;
      }
    }

    container cargo {
      presence "some deep meaning";
    }
  }

  container test3 {
    list complex-list {
      key "type name";

      leaf type {
        type string;
      }

      leaf name {
        type string;
      }

      leaf data {
        type string;
      }
    }
  }

  container test4 {
    leaf-list params {
      type string;
    }
  }

  rpc clear-stats {
    description
      "An RPC with inputs and outputs.";
    input {
      leaf interface {
        type string;
      }
      leaf errors {
        type empty;
        description
          "clear only error stats";
      }
    }
    output {
      leaf old-stats {
        type uint64;
      }
    }
  }

  rpc no-subscriber {
    description
      "An RPC that has no subscriber registered.";
    input {
      leaf foo {
        type string;
      }
    }
  }

  container action-test {
    action action-test {
      description
        "An action with input and output.";
      input {
        leaf foo {
          type string;
        }
      }
      output {
        leaf bar {
          type string;
        }
      }
    }
  }
}
