module gnmi-server-test-wine {
  yang-version 1.1;
  namespace "https://graphiant.com/gnmi-server-test-wine";
  prefix test;

  import openconfig-extensions {
    prefix oc-ext;
  }

  description
    "gNMI Server Test module
        Copyright (c) 2025 Graphiant, Inc.
        All rights reserved.
        Licensed under the Apache License, Version 2.0 (the 'License');
        you may not use this file except in compliance with the License.
        You may obtain a copy of the License at

        http://www.apache.org/licenses/LICENSE-2.0

        Unless required by applicable law or agreed to in writing, software
        distributed under the License is distributed on an 'AS IS' BASIS,
        WITHOUT WARRANTIES OR CONDITIONS OF ANY KIND, either express or implied.
        See the License for the specific language governing permissions and
        limitations under the License.
    ";

  // bind this module to the rfc7951 origin only
  oc-ext:origin rfc7951;

  revision 2022-04-27 {
    description
      "Initial revision";
  }

  container wines {
    list wine {
      key "name vintage";

      leaf name {
        type string;
      }

      leaf vintage {
        type uint32 {
	  range "1900..2100";
	}
      }

      leaf score {
        type uint32 {
	  range "0..100";
	}
      }
    }
  }
}
